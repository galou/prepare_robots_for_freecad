# Create files of Yaskawa GP180-120 robot for FreeCAD's Robot Workbench.
#
# Create a WRL and Kinematics CSV file of the Yaskawa GP180-120 robot.
#
# License: 'LGPL-2.0-or-later'
# Copyright 2026 FreeCAD Developers

import tempfile
import shutil
from pathlib import Path

import FreeCAD as app
from FreeCAD import Placement, Rotation, Vector

from prepare_robots_utils import (
        download_original,
        import_original,
        include_vrml_file,
        save_files,
        save_obj_as_wrl,
        write_csv,
        ImportOptions,
        Robot,
        DHFrame,
        X_AXIS,
        Z_AXIS,
)


def create_wrl(doc: app.Document, file_path: Path) -> None:
    """Export the robot model to a WRL file."""
    directory = file_path.parent

    known_labels: list[str] = [o.Label for o in doc.Objects]

    # Bring the complete robot z-up, TCP x+ with all axes at 0°..
    global_transform = Placement(
        Vector(0.0, 0.0, 0.0),
        Rotation(X_AXIS, -90) * Rotation(Z_AXIS, 180),
    )
    try:
        base_wrl = save_obj_as_wrl(
                doc,
                "BASE_AXIS",
                global_transform,
                directory,
        )
    except ValueError:
        msg = f'Could not find "BASE_AXIS" object in the document, document objects are {known_labels}.'
        app.Console.PrintError(msg + "\n")
        raise

    s_placement = Placement(Vector(0, 0, 650), Rotation(0, 0, 0))
    try:
        s_wrl = save_obj_as_wrl(
                doc,
                "S_AXIS",
                global_transform,
                directory,
        )
    except ValueError:
        msg = f'Could not find "S_AXIS" object in the document, document objects are {known_labels}.'
        app.Console.PrintError(msg + "\n")
        raise

    l_placement = Placement(Vector(325, 0, 650), Rotation(0, 0, -90))
    try:
        l_wrl = save_obj_as_wrl(
                doc,
                "L_AXIS",
                global_transform,
                directory,
        )
    except ValueError:
        msg = f'Could not find "L_AXIS" object in the document, document objects are {known_labels}.'
        app.Console.PrintError(msg + "\n")
        raise

    u_placement = Placement(Vector(325, 0, 1800), Rotation(0, 0, -90))
    try:
        u_wrl = save_obj_as_wrl(
                doc,
                "U_AXIS",
                global_transform,
                directory,
        )
    except ValueError:
        msg = f'Could not find "U_AXIS" object in the document, document objects are {known_labels}.'
        app.Console.PrintError(msg + "\n")
        raise

    r_placement = Placement(Vector(325, 0, 2100), Rotation(90, 0, 90))
    try:
        r_wrl = save_obj_as_wrl(
                doc,
                "R_AXIS",
                global_transform,
                directory,
        )
    except ValueError:
        msg = f'Could not find "R_AXIS" object in the document, document objects are {known_labels}.'
        app.Console.PrintError(msg + "\n")
        raise

    b_placement = Placement(Vector(1915, 0, 2100), Rotation(0, 0, -90))
    try:
        b_wrl = save_obj_as_wrl(
                doc,
                "B_AXIS",
                global_transform,
                directory,
        )
    except ValueError:
        msg = f'Could not find "B_AXIS" object in the document, document objects are {known_labels}.'
        app.Console.PrintError(msg + "\n")
        raise

    t_placement = Placement(Vector(2140, 0, 2100), Rotation(90, 0,90))
    try:
        t_wrl = save_obj_as_wrl(
                doc,
                "T_AXIS",
                global_transform,
                directory,
        )
    except ValueError:
        msg = f'Could not find "T_AXIS" object in the document, document objects are {known_labels}.'
        app.Console.PrintError(msg + "\n")
        raise

    files = [s_wrl, l_wrl, u_wrl, r_wrl, b_wrl, t_wrl]

    # How to obtain placements:
    # - Load the URDF with the CROSS workbench.
    # - App.ActiveDocument.motoman_gp180_120.Rotation = Rotation(180, 0, 90)
    # - turn_axis = Rotation(180, 0, 90)
    # - pl_2_l = App.ActiveDocument.joint_2_l.Placement * turn_axis
    placements = [
            s_placement,
            l_placement,
            u_placement,
            r_placement,
            b_placement,
            t_placement,
    ]
    before_parts = []
    after_parts = []
    indent = "    "
    for i in range(len(files)):
        t = placements[i] * global_transform
        before, after = include_vrml_file(files[i], axis=i + 1, joint_transform=t, indent=indent)
        before_parts.append(before)
        after_parts.append(after)
        indent += "  "

    output_wrl_path = directory / "gp180-120.wrl"
    with output_wrl_path.open("w") as f:
        f.write("#VRML V2.0 utf8\n")
        f.write("DEF GP180_120 Group {\n")
        f.write("  children [\n")
        with base_wrl.open("r") as base_f:
            for line in base_f:
                f.write("    " + line)
        for before in before_parts:
            f.write(before)
        for after in reversed(after_parts):
            f.write(after)
        f.write("  ]\n")
        f.write("}\n")


def create_csv(file_path: Path) -> None:
    lengths = [650.0, 325.0, 1150.0, 300.0, 1590.0,  225.0]
    # d =     ([lengths[0],          0,          0, -lengths[4],       0, -lengths[5]]),
    # theta = ([         0,    -M_PI_2,          0,           0,       0,           0]),
    # r =     ([lengths[1], lengths[2], lengths[3],           0,       0,           0]),
    # alpha = ([   -M_PI_2,       M_PI,    -M_PI_2,      M_PI_2, -M_PI_2,        M_PI]),
    kinematics = Robot([
        DHFrame(d=lengths[0],  theta=0.0,   r=lengths[1], alpha=-90.0, min_angle=-180.0, max_angle=180.0, velocity=125.0),
        DHFrame(d=0.0,         theta=-90.0, r=lengths[2], alpha=180.0, min_angle=-60.0,  max_angle=76.0,  velocity=115.0),
        DHFrame(d=0.0,         theta=0.0,   r=lengths[3], alpha=-90.0, min_angle=-86.0,  max_angle=90.0,  velocity=125.0),
        DHFrame(d=-lengths[4], theta=0.0,   r=0.0,        alpha=90.0,  min_angle=-360.0, max_angle=360.0, velocity=182.0),
        DHFrame(d=0.0,         theta=0.0,   r=0.0,        alpha=-90.0, min_angle=-130.0, max_angle=130.0, velocity=175.0),
        DHFrame(d=-lengths[5], theta=0.0,   r=0.0,        alpha=180.0, min_angle=-360.0, max_angle=360.0, velocity=265.0),
    ])

    write_csv(file_path, kinematics)


def main():
    temp_dir = Path(tempfile.mkdtemp())

    try:
        step_paths = download_original(
                url="https://www.yaskawa.eu.com/_downloads/download_d3360",
                member_paths=["GP180_120_3D/gp180-120.stp"],
                dest_dir_path=temp_dir,
        )
    except ValueError:
        shutil.rmtree(temp_dir)
        return
    if step_paths is None:
        shutil.rmtree(temp_dir)
        return

    doc = app.newDocument("GP180_120", temp=True, hidden=True)

    import_options = ImportOptions(
            format="STEP",
            step_merge_compounds=True,
    )
    import_original(doc, step_paths, import_options)

    # Adjust orientation to have Z up, TCP at X+,Y0 at home position.
    # TODO(Gaël): this has no effect since the part transform is not taken into account
    # when exporting. To correctly export, the transform has to be applied to the
    # indivual objects.
    # robot_obj = doc.getObjectsByLabel("gp180-120")[0]
    # robot_obj.Placement.Rotation = Rotation(Vector(1, 0, 0), -90) * Rotation(Vector(0, 0, 1), 180)
    # doc.recompute()

    # Write the Kinematics file.
    output_csv_path = temp_dir / "gp180-120_kinematics.csv"
    create_csv(output_csv_path)

    output_wrl_path = temp_dir / "gp180-120.wrl"
    create_wrl(doc, output_wrl_path)

    save_files([output_csv_path, output_wrl_path], temp_dir)

    app.closeDocument(doc.Name)
    shutil.rmtree(temp_dir)


if __name__ == "__main__":
    main()
